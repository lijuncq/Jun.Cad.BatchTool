(defun s2 (v) (cond ((= (type v) 'STR) v) ((null v) "") ((numberp v) (rtos v 2 4)) (T "")))
(setq f (open (strcat (getvar "DWGPREFIX") "dump.txt") "w"))
(princ (strcat "ACADVER=" (getvar "ACADVER") "\n") f)
(setq ss (ssget "_X"))
(princ (strcat "ENTCOUNT=" (itoa (sslength ss)) "\n") f)
(setq i 0)
(repeat (sslength ss)
  (setq d (entget (ssname ss i)))
  (princ (strcat "E|" (s2 (cdr (assoc 0 d))) "|" (s2 (cdr (assoc 8 d))) "|" (s2 (cdr (assoc 62 d))) "|" (s2 (cdr (assoc 6 d))) "|" (s2 (cdr (assoc 3 d))) "\n") f)
  (if (= (cdr (assoc 0 d)) "HATCH")
    (princ (strcat "H|" (s2 (cdr (assoc 2 d))) "|" (s2 (cdr (assoc 41 d))) "|" (s2 (cdr (assoc 52 d))) "\n") f)
  )
  (if (member (cdr (assoc 0 d)) (list "TEXT" "MTEXT" "ATTRIB" "ATTDEF"))
    (princ (strcat "T|" (s2 (cdr (assoc 7 d))) "|" (s2 (cdr (assoc 40 d))) "\n") f)
  )
  (if (= (cdr (assoc 0 d)) "INSERT")
    (princ (strcat "I|" (s2 (cdr (assoc 2 d))) "\n") f)
  )
  (setq i (1+ i))
)
(setq ln (tblnext "LAYER" T))
(while ln
  (princ (strcat "L|" (s2 (cdr (assoc 2 ln))) "|" (s2 (cdr (assoc 62 ln))) "|" (s2 (cdr (assoc 6 ln))) "|" (s2 (cdr (assoc 370 ln))) "\n") f)
  (setq ln (tblnext "LAYER"))
)
(setq bn (tblnext "BLOCK" T))
(while bn
  (setq bname (cdr (assoc 2 bn)))
  (princ (strcat "B|" bname "\n") f)
  (setq be (tblobjname "BLOCK" bname))
  (if be
    (progn
      (setq ce (entnext be))
      (while ce
        (setq cd (entget ce))
        (princ (strcat "BI|" bname "|" (s2 (cdr (assoc 0 cd))) "|" (s2 (cdr (assoc 8 cd))) "\n") f)
        (setq ce (entnext ce))
      )
    )
  )
  (setq bn (tblnext "BLOCK"))
)
(setq sn (tblnext "STYLE" T))
(while sn
  (princ (strcat "S|" (s2 (cdr (assoc 2 sn))) "|" (s2 (cdr (assoc 3 sn))) "|" (s2 (cdr (assoc 4 sn))) "|" (s2 (cdr (assoc 41 sn))) "\n") f)
  (setq sn (tblnext "STYLE"))
)
(setq dn (tblnext "DIMSTYLE" T))
(while dn
  (princ (strcat "D|" (s2 (cdr (assoc 2 dn))) "|" (s2 (cdr (assoc 140 dn))) "|" (s2 (cdr (assoc 41 dn))) "\n") f)
  (setq dn (tblnext "DIMSTYLE"))
)
(setq tn (tblnext "LTYPE" T))
(while tn
  (princ (strcat "LT|" (s2 (cdr (assoc 2 tn))) "\n") f)
  (setq tn (tblnext "LTYPE"))
)
(close f)
(princ "DUMP_DONE")
(quit)
