(defun s2 (v) (cond ((= (type v) 'STR) v) ((null v) "") ((numberp v) (rtos v 2 4)) (T "")))
(setq f (open (strcat (getvar "DWGPREFIX") "hatch.txt") "w"))
(setq ss (ssget "_X" '((0 . "HATCH"))))
(setq i 0)
(repeat (sslength ss)
  (setq d (entget (ssname ss i)))
  (princ (strcat "HATCH|name=" (s2 (cdr (assoc 2 d)))
                 "|solid=" (s2 (cdr (assoc 70 d)))
                 "|assoc=" (s2 (cdr (assoc 71 d)))
                 "|scale=" (s2 (cdr (assoc 41 d)))
                 "|angle=" (s2 (cdr (assoc 52 d)))
                 "|style=" (s2 (cdr (assoc 75 d)))
                 "|ptype=" (s2 (cdr (assoc 76 d)))
                 "|double=" (s2 (cdr (assoc 77 d)))
                 "|plines=" (s2 (cdr (assoc 78 d)))
                 "|paths=" (s2 (cdr (assoc 91 d)))
                 "|grad=" (s2 (cdr (assoc 450 d)))
                 "|gname=" (s2 (cdr (assoc 470 d)))
                 "|gsingle=" (s2 (cdr (assoc 451 d)))
                 "|gang=" (s2 (cdr (assoc 452 d)))
                 "|gshift=" (s2 (cdr (assoc 453 d)))
                 "\n") f)
  (setq i (1+ i))
)
(close f)
(princ "HATCH_DONE")
(quit)
