(defun s2 (v) (cond ((= (type v) 'STR) v) ((null v) "") ((numberp v) (rtos v 2 4)) (T "")))
(defun dumpent (e tag f)
  (setq d (entget e))
  (if (= (cdr (assoc 0 d)) "HATCH")
    (princ (strcat "H|" tag "|" (s2 (cdr (assoc 2 d)))
                   "|scale=" (s2 (cdr (assoc 41 d)))
                   "|angle=" (s2 (cdr (assoc 52 d)))
                   "|ptype=" (s2 (cdr (assoc 76 d)))
                   "|plines=" (s2 (cdr (assoc 78 d)))
                   "|paths=" (s2 (cdr (assoc 91 d)))
                   "\n") f)
  )
)
(setq f (open (strcat (getvar "DWGPREFIX") "blockhatch.txt") "w"))
(setq ss (ssget "_X" '((0 . "HATCH"))))
(setq i 0)
(repeat (sslength ss)
  (dumpent (ssname ss i) "space" f)
  (setq i (1+ i))
)
(setq bn (tblnext "BLOCK" T))
(while bn
  (setq bname (cdr (assoc 2 bn)))
  (if (not (wcmatch bname "*Model_Space,*Paper_Space"))
    (progn
      (setq be (tblobjname "BLOCK" bname))
      (if be
        (progn
          (setq ce (entnext be))
          (while ce
            (dumpent ce (strcat "block:" bname) f)
            (setq ce (entnext ce))
          )
        )
      )
    )
  )
  (setq bn (tblnext "BLOCK"))
)
(close f)
(princ "BH_DONE")
(quit)
