(defun s2 (v) (cond ((= (type v) 'STR) v) ((null v) "") ((numberp v) (rtos v 2 4)) (T "")))
(setq f (open (strcat (getvar "DWGPREFIX") "hatchraw.txt") "w"))
(setq ss (ssget "_X" '((0 . "HATCH"))))
(setq i 0)
(repeat (sslength ss)
  (setq d (entget (ssname ss i)))
  (princ (strcat "---- HATCH " (itoa i) " ----\n") f)
  (foreach pr d
    (setq c (car pr))
    (if (member c (list 2 41 43 44 45 46 47 49 52 53 70 71 75 76 77 78 79 91 450 451 452 453 460 461 462 463 470))
      (princ (strcat (itoa c) "=" (s2 (cdr pr)) "\n") f)
    )
  )
  (setq i (1+ i))
)
(close f)
(princ "RAW_DONE")
(quit)
