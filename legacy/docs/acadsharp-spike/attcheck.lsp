(defun s2 (v) (cond ((= (type v) 'STR) v) ((null v) "") ((numberp v) (rtos v 2 4)) (T "")))
(setq f (open (strcat (getvar "DWGPREFIX") "att.txt") "w"))
(setq ss (ssget "_X" '((0 . "INSERT"))))
(setq i 0)
(repeat (sslength ss)
  (setq e (ssname ss i))
  (setq d (entget e))
  (setq bn (cdr (assoc 2 d)))
  (setq cnt 0)
  (setq sub (entnext e))
  (while (and sub (/= (cdr (assoc 0 (entget sub))) "SEQEND"))
    (setq sd (entget sub))
    (if (= (cdr (assoc 0 sd)) "ATTRIB")
      (progn
        (setq cnt (1+ cnt))
        (princ (strcat "A|" bn "|" (s2 (cdr (assoc 2 sd))) "|" (s2 (cdr (assoc 1 sd))) "\n") f)
      )
    )
    (setq sub (entnext sub))
  )
  (princ (strcat "N|" bn "|" (itoa cnt) "\n") f)
  (setq i (1+ i))
)
(close f)
(princ "ATT_DONE")
(quit)
